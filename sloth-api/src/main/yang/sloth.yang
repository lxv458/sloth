module sloth-permission {
    yang-version 1;
    namespace "urn:opendaylight:params:xml:ns:yang:sloth";
    prefix "sloth";

    revision "2015-01-05" {
        description "Initial revision of sloth model";
    }

    rpc check-permission {
        input {
            container permission-user {
                leaf user-name {
                    type string;
                }
                leaf user-id {
                    type string;
                }
                leaf domain {
                    type string;
                }
                list roles {
                    key "role";
                    leaf role {
                        type string;
                    }
                }
            }
            container permission-request {
                leaf method {
                    type string;
                /*
                    type enumeration {
                        enum GET;
                        enum PUT;
                        enum POST;
                        enum DELETE;
                        enum HEAD;
                        enum OPTIONS;
                        enum CONNECT;
                    }
                */
                }
                leaf request-url {
                    type string;
                }
                leaf query-string {
                    type string;
                }
                leaf json-body {
                    type string;
                }
            }
        }
        output {
            leaf permission {
                type string;
            }
        }
    }
}
