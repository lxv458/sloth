module sloth-model {
    yang-version 1;
    namespace "urn:opendaylight:sloth:model";
    prefix "sloth-model";

    import "sloth-permission" {
        prefix "spermission";
    }

    revision "2015-01-05" {
        description "Initial revision of sloth-model model";
    }


    grouping policies {
        list policy-set {
            key "id";
            leaf id {
                type string;
            }
            leaf name {
                type string;
            }
            leaf content {
                type string;
            }
        }
    }

    container sloth-policy-hub {
        container global-policy-set {
            uses policies;
        }
        list local-policy-set {
            key "id";
            leaf id {
                type string;
            }
            uses policies;
        }
    }

    container domains {
        list domain {
            key "id";
            leaf id {
                type string;
            }
            leaf name {
                type string;
            }
            list role {
                key "id";
                leaf id {
                    type string;
                }
                leaf name {
                    type string;
                }
                leaf priority {
                    type uint16;
                }
                leaf-list permission-id {
                    type string;
                }
                leaf disabled {
                    type boolean;
                    default false;
                }
            }
            leaf disabled {
                type boolean;
                default false;
            }
        }
    }

    grouping param-check {
        leaf param {
            type string;
        }
        leaf-list value {
            type string;
        }
    }

    container permissions {
        list permission {
            key "id";
            leaf id {
                type string;
            }
            leaf name {
                type string;
            }
            leaf-list resource {
                type string;
            }
            leaf-list action {
                type spermission:http-type;
            }
            list param-query {
                uses param-check;
            }
            list param-json {
                uses param-check;
            }
            leaf disabled {
                type boolean;
                default false;
            }
        }
    }
}
