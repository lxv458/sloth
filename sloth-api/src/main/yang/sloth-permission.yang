module sloth-permission {
    yang-version 1;
    namespace "urn:opendaylight:sloth:permission";
    prefix "sloth-permission";

    revision "2015-01-05" {
        description "Initial revision of sloth permission model";
    }

    typedef http-type {
        type enumeration {
            enum GET;
            enum PUT;
            enum POST;
            enum DELETE;
        }
    }

    rpc check-permission {
        input {
            container principal {
                leaf user-name {
                    type string;
                }
                leaf user-id {
                    type string;
                }
                leaf domain {
                    type string;
                }
                leaf-list roles {
                    type string;
                }
            }
            container request {
                leaf method {
                    type http-type;
                }
                leaf request-url {
                    type string;
                }
                leaf query-string {
                    type string;
                }
                leaf json-body {
                    type string;
                }
            }
        }
        output {
            leaf status-code {
                type uint16;
            }
            leaf response {
                type string;
            }
        }
    }
}
